/*
 * Copyright (C) 2024 - 2025 NVIDIA CORPORATION & AFFILIATES
 * Copyright (C) 2021 - 2024 AdaCore
 *
 * Permission is granted to copy, distribute and/or modify this document
 * under the terms of the GNU Free Documentation License, Version 1.3 or
 * any later version published by the Free Software Foundation; with the
 * Invariant Sections being "Attribution", with no Front-Cover
 * Texts, and no Back-Cover Texts.  A copy of the license is included in
 * the section entitled "GNU Free Documentation License".
 */

package Switches

// from compiler_banned.csv, row 1
Compiler_Switch_Constraint Compiler_Switch_gnata {
   warn_related = false
   status       = Status.Banned
   switches     = [
     // (except for non-production builds)
     Pattern.Prefix: "-gnata"
   ]
   rationale    = '''
     This switch causes contracts to be executed at runtime, and
     contracts and ghost code are permitted to use Ada 2022, but Ada
     2022 is not safety qualified for production use.
   '''
}

// from compiler_banned.csv, row 2
Compiler_Switch_Constraint Compiler_Switch_RTS {
   warn_related = false
   status       = Status.Banned
   switches     = [
     Pattern.Prefix: "--RTS"
   ]
   rationale    = '''
     The runtime should be set at project level.
   '''
}

// from compiler_banned.csv, row 3
Compiler_Switch_Constraint Compiler_Switch_Group_1 {
   warn_related = false
   status       = Status.Banned
   switches     = [
     Pattern.Prefix: "-c",
     // <file>
     Pattern.Prefix: "-o",
     // <path>
     Pattern.Prefix: "-I",
     Pattern.Prefix: "-x",
     Pattern.Prefix: "-S"
   ]
   rationale    = '''
     Will be added by gprbuild.
   '''
}

// from compiler_banned.csv, row 4
Compiler_Switch_Constraint Compiler_Switch_All {
   warn_related = false
   status       = Status.Banned
   switches     = [
     // non-warning-related compiler switches not explicitly listed in the compiler safety manual as having been safety qualified
     Pattern.Prefix: "All"
   ]
   rationale    = '''
     These compiler switches are not safety-qualified.
   '''
}

// from compiler_optional.csv, row 1
Compiler_Switch_Constraint Compiler_Switch_Group_2 {
   warn_related = false
   status       = Status.Allowed
   switches     = [
     Pattern.Prefix: "-gnato",
     Pattern.Prefix: "-gnaton",
     Pattern.Prefix: "-gnatomn"
   ]
   rationale    = '''
     The ``-gnato`` family of switches is permitted but not
     recommended. The ``-gnato0`` switch suppresses overflow checks
     (except where explicitly unsuppressed in the code, such as for
     all non-SPARK code). Overflow checks are just one of the kinds of
     checks suppressed by the ``-gnatp`` switch. The ``-gnato0``
     switch is permitted for the same reasons that the ``-gnatp``
     switch is permitted. However, for performance reasons, it is
     preferable to use the ``-gnatp`` switch instead, as it suppresses
     more unnecessary checks. The ``-gnato``, ``-gnato1``, and
     ``-gnato11`` switches all have the effect of enabling overflow
     checking (even in SPARK code), without changing the overflow mode
     from the default (STRICT both inside and outside of contracts).
     This can undo the beneficial performance effects of ``-gnatp``.
     The ``-gnato2``, ``-gnato3``, ``-gnato12``, ``-gnato13``,
     ``-gnato21``, ``-gnato22``, ``-gnato23``, and ``-gnato33``
     switches unnecessarily widen intermediate subexpressions in SPARK
     code (where GNATprove already formally verifies the absence of
     overflow even without the widening), potentially hurting
     performance of SPARK code. These switches can also make it more
     difficult to determine whether a non-SPARK Ada code computation
     will complete successfully or trigger a language-defined check,
     reducing the clarity of non-SPARK Ada code. Note: The
     :ref:`Verify_Dynamic_Assumptions
     <step-verify-dynamic-assumptions>` and
     :ref:`Run_Integration_Tests <step-run-integration-tests>` steps
     require rebuilding tests without the ``-gnato0`` switch.
   '''
}

// from compiler_optional.csv, row 2
Compiler_Switch_Constraint Compiler_Switch_gnatp {
   warn_related = false
   status       = Status.Allowed
   switches     = [
     // (except for non-production builds)
     Pattern.Prefix: "-gnatp"
   ]
   rationale    = '''
     The ``-gnatp`` switch disables unnecessary language-defined
     checks in SPARK code and may thereby improve the performance of
     SPARK code. The checks are unnecessary because GNATprove formally
     verifies that SPARK code never violates any of the properties
     checked by the language-defined checks. This switch is not
     required, but it is recommended by this process for performance
     reasons. Note: This process requires all non-SPARK code to be
     contained within pragma Unsuppress(All_Checks) regions.
     Therefore, in software units that comply with this process,
     non-SPARK code is not affected by the presence or absence of the
     ``-gnatp`` switch. Note: The :ref:`Verify_Dynamic_Assumptions
     <step-verify-dynamic-assumptions>` and
     :ref:`Run_Integration_Tests <step-run-integration-tests>` steps
     require rebuilding tests without the ``-gnatp`` switch.
   '''
}

// from compiler_required.csv, row 1
Compiler_Switch_Constraint Compiler_Switch_fcallgraph_info {
   warn_related = false
   status       = Status.Required
   switches     = [
     Pattern.Prefix: "-fcallgraph-info=su,da"
   ]
   rationale    = '''
     Necessary to ensure that GNATstack produces correct output in the
     Check_Stack_Usage step.
   '''
}

// from compiler_required.csv, row 2
Compiler_Switch_Constraint Compiler_Switch_gnatyr {
   warn_related = false
   status       = Status.Required
   switches     = [
     Pattern.Prefix: "-gnatyr"
   ]
   rationale    = '''
     Unique IDs (see section Traceability Model) are case sensitive
     and built from local IDs sometimes derived from identifiers. To
     remove ambiguity concerning the correct local ID (and thus the
     correct unique ID) for a comment or syntactic construct, all
     references to the same entity must agree about the case of the
     associated identifiers.
   '''
}

// from compiler_warning_banned.csv, row 1
Compiler_Switch_Constraint Compiler_Switch_Group_3 {
   warn_related = true
   status       = Status.Banned
   switches     = [
     Pattern.Prefix: "-gnatwA",
     Pattern.Prefix: "-gnatw.A",
     Pattern.Prefix: "-gnatw_A",
     Pattern.Prefix: "-gnatwB",
     Pattern.Prefix: "-gnatw.B",
     Pattern.Prefix: "-gnatwC",
     Pattern.Prefix: "-gnatw.C",
     Pattern.Prefix: "-gnatw_C",
     Pattern.Prefix: "-gnatwF",
     Pattern.Prefix: "-gnatwG",
     Pattern.Prefix: "-gnatwI",
     Pattern.Prefix: "-gnatw.I",
     Pattern.Prefix: "-gnatwJ",
     Pattern.Prefix: "-gnatwK",
     Pattern.Prefix: "-gnatwM",
     Pattern.Prefix: "-gnatw.M",
     Pattern.Prefix: "-gnatwP",
     Pattern.Prefix: "-gnatw.P",
     Pattern.Prefix: "-gnatw_P",
     Pattern.Prefix: "-gnatwQ",
     Pattern.Prefix: "-gnatwR",
     Pattern.Prefix: "-gnatw.R",
     Pattern.Prefix: "-gnatw.T",
     Pattern.Prefix: "-gnatwU",
     Pattern.Prefix: "-gnatwV",
     Pattern.Prefix: "-gnatw.V",
     Pattern.Prefix: "-gnatwW",
     Pattern.Prefix: "-gnatwX",
     Pattern.Prefix: "-gnatwY",
     Pattern.Prefix: "-gnatwZ",
     Pattern.Prefix: "-gnatw.Z"
   ]
   rationale    = '''
     Would suppress warnings enabled by ``-gnatwa``
   '''
}

// from compiler_warning_banned.csv, row 2
Compiler_Switch_Constraint Compiler_Switch_Warning_Uppercase_Dot_D {
   warn_related = true
   status       = Status.Banned
   switches     = [
     Pattern.Prefix: "-gnatw.D"
   ]
   rationale    = '''
     Would suppress effects of ``-gnatw.d``
   '''
}

// from compiler_warning_banned.csv, row 3
Compiler_Switch_Constraint Compiler_Switch_Warning_UppercaseH {
   warn_related = true
   status       = Status.Banned
   switches     = [
     Pattern.Prefix: "-gnatwH"
   ]
   rationale    = '''
     Would suppress effects of ``-gnatwh``
   '''
}

// from compiler_warning_banned.csv, row 4
Compiler_Switch_Constraint Compiler_Switch_Warning_Uppercase_Dot_H {
   warn_related = true
   status       = Status.Banned
   switches     = [
     Pattern.Prefix: "-gnatw.H"
   ]
   rationale    = '''
     Would suppress effects of ``-gnatw.h``
   '''
}

// from compiler_warning_banned.csv, row 5
Compiler_Switch_Constraint Compiler_Switch_Warning_Uppercase_Dot_J {
   warn_related = true
   status       = Status.Banned
   switches     = [
     Pattern.Prefix: "-gnatw.J"
   ]
   rationale    = '''
     Would suppress effects of ``-gnatw.j``
   '''
}

// from compiler_warning_banned.csv, row 6
Compiler_Switch_Constraint Compiler_Switch_Warning_Uppercase_Dot_K {
   warn_related = true
   status       = Status.Banned
   switches     = [
     Pattern.Prefix: "-gnatw.K"
   ]
   rationale    = '''
     Would suppress effects of ``-gnatw.k``
   '''
}

// from compiler_warning_banned.csv, row 7
Compiler_Switch_Constraint Compiler_Switch_Warning_UppercaseL {
   warn_related = true
   status       = Status.Banned
   switches     = [
     Pattern.Prefix: "-gnatwL"
   ]
   rationale    = '''
     Would suppress effects of ``-gnatwl``
   '''
}

// from compiler_warning_banned.csv, row 8
Compiler_Switch_Constraint Compiler_Switch_Warning_Lowercasen {
   warn_related = true
   status       = Status.Banned
   switches     = [
     Pattern.Prefix: "-gnatwn"
   ]
   rationale    = '''
     Would suppress effects of ``-gnatwe``
   '''
}

// from compiler_warning_banned.csv, row 9
Compiler_Switch_Constraint Compiler_Switch_Warning_UppercaseO {
   warn_related = true
   status       = Status.Banned
   switches     = [
     Pattern.Prefix: "-gnatwO"
   ]
   rationale    = '''
     Would disable some warnings that are enabled by default
   '''
}

// from compiler_warning_banned.csv, row 10
Compiler_Switch_Constraint Compiler_Switch_Warning_Uppercase_Dot_O {
   warn_related = true
   status       = Status.Banned
   switches     = [
     Pattern.Prefix: "-gnatw.O"
   ]
   rationale    = '''
     Would suppress effects of ``-gnatw.o``
   '''
}

// from compiler_warning_banned.csv, row 11
Compiler_Switch_Constraint Compiler_Switch_Warning_Uppercase_Underscore_R {
   warn_related = true
   status       = Status.Banned
   switches     = [
     Pattern.Prefix: "-gnatw_R"
   ]
   rationale    = '''
     Would suppress effects of ``-gnatw_r``
   '''
}

// from compiler_warning_banned.csv, row 12
Compiler_Switch_Constraint Compiler_Switch_Warning_Lowercases {
   warn_related = true
   status       = Status.Banned
   switches     = [
     Pattern.Prefix: "-gnatws"
   ]
   rationale    = '''
     Would disable all warnings
   '''
}

// from compiler_warning_banned.csv, row 13
Compiler_Switch_Constraint Compiler_Switch_Warning_Uppercase_Dot_S {
   warn_related = true
   status       = Status.Banned
   switches     = [
     Pattern.Prefix: "-gnatw.S"
   ]
   rationale    = '''
     Would suppress effects of ``-gnatw.s``
   '''
}

// from compiler_warning_banned.csv, row 14
Compiler_Switch_Constraint Compiler_Switch_Warning_UppercaseT {
   warn_related = true
   status       = Status.Banned
   switches     = [
     Pattern.Prefix: "-gnatwT"
   ]
   rationale    = '''
     Would suppress effects of ``-gnatwt``
   '''
}

// from compiler_warning_banned.csv, row 15
Compiler_Switch_Constraint Compiler_Switch_Warning_Uppercase_Dot_W {
   warn_related = true
   status       = Status.Banned
   switches     = [
     Pattern.Prefix: "-gnatw.W"
   ]
   rationale    = '''
     Would suppress effects of ``-gnatw.w``
   '''
}

// from compiler_warning_banned.csv, row 16
Compiler_Switch_Constraint Compiler_Switch_Warning_Lowercase_Dot_x {
   warn_related = true
   status       = Status.Banned
   switches     = [
     Pattern.Prefix: "-gnatw.x"
   ]
   rationale    = '''
     Would undo effects of ``-gnatw``.X
   '''
}

// from compiler_warning_banned.csv, row 17
Compiler_Switch_Constraint Compiler_Switch_w {
   warn_related = true
   status       = Status.Banned
   switches     = [
     Pattern.Prefix: "-w"
   ]
   rationale    = '''
     Would undo effects of -Wall
   '''
}

// from compiler_warning_optional.csv, row 1
Compiler_Switch_Constraint Compiler_Switch_Group_4 {
   warn_related = true
   status       = Status.Allowed
   switches     = [
     Pattern.Prefix: "-gnatw.a",
     Pattern.Prefix: "-gnatw_a",
     Pattern.Prefix: "-gnatwb",
     Pattern.Prefix: "-gnatw.b",
     Pattern.Prefix: "-gnatwc",
     Pattern.Prefix: "-gnatw.c",
     Pattern.Prefix: "-gnatw_c",
     Pattern.Prefix: "-gnatwf",
     Pattern.Prefix: "-gnatwg",
     Pattern.Prefix: "-gnatwi",
     Pattern.Prefix: "-gnatw.i",
     Pattern.Prefix: "-gnatwj",
     Pattern.Prefix: "-gnatwk",
     Pattern.Prefix: "-gnatwm",
     Pattern.Prefix: "-gnatw.m",
     Pattern.Prefix: "-gnatwp",
     Pattern.Prefix: "-gnatw.p",
     Pattern.Prefix: "-gnatw_p",
     Pattern.Prefix: "-gnatwq",
     Pattern.Prefix: "-gnatwr",
     Pattern.Prefix: "-gnatw.r",
     Pattern.Prefix: "-gnatw.t",
     Pattern.Prefix: "-gnatwu",
     Pattern.Prefix: "-gnatwv",
     Pattern.Prefix: "-gnatw.v",
     Pattern.Prefix: "-gnatww",
     Pattern.Prefix: "-gnatwx",
     Pattern.Prefix: "-gnatwy",
     Pattern.Prefix: "-gnatwz",
     Pattern.Prefix: "-gnatw.z"
   ]
   rationale    = '''
     Would have no effect (already enabled by required switch
     ``-gnatwa``)
   '''
}

// from compiler_warning_optional.csv, row 2
Compiler_Switch_Constraint Compiler_Switch_Group_5 {
   warn_related = true
   status       = Status.Allowed
   switches     = [
     Pattern.Prefix: "-gnatwd",
     Pattern.Prefix: "-gnatwD"
   ]
   rationale    = '''
     Enabling the warnings would disallow a common idiom in Ada that
     is prevalent even among Ada examples
   '''
}

// from compiler_warning_optional.csv, row 3
Compiler_Switch_Constraint Compiler_Switch_Warning_UppercaseE {
   warn_related = true
   status       = Status.Allowed
   switches     = [
     Pattern.Prefix: "-gnatwE"
   ]
   rationale    = '''
     All warnings enabled by this switch are already enabled by
     ``-gnatwe``
   '''
}

// from compiler_warning_optional.csv, row 4
Compiler_Switch_Constraint Compiler_Switch_Warning_Lowercase_Dot_e {
   warn_related = true
   status       = Status.Allowed
   switches     = [
     Pattern.Prefix: "-gnatw.e"
   ]
   rationale    = '''
     AdaCore documentation warns that this switch is "almost certain"
     to cause "large numbers of useless warnings"
   '''
}

// from compiler_warning_optional.csv, row 5
Compiler_Switch_Constraint Compiler_Switch_Warning_Lowercase_Dot_g {
   warn_related = true
   status       = Status.Allowed
   switches     = [
     Pattern.Prefix: "-gnatw.g"
   ]
   rationale    = '''
     Entirely redundant with other warning options, and AdaCore warns
     that its effect may change in the future without advanced notice
   '''
}

// from compiler_warning_optional.csv, row 6
Compiler_Switch_Constraint Compiler_Switch_Group_6 {
   warn_related = true
   status       = Status.Allowed
   switches     = [
     Pattern.Prefix: "-gnatw.l",
     Pattern.Prefix: "-gnatw.L"
   ]
   rationale    = '''
     This switch merely causes the compiler to emit a list of aspects
     that are inherited, which is purely informational, rather than a
     list of things that are wrong.
   '''
}

// from compiler_warning_optional.csv, row 7
Compiler_Switch_Constraint Compiler_Switch_Group_7 {
   warn_related = true
   status       = Status.Allowed
   switches     = [
     Pattern.Prefix: "-gnatw.n",
     Pattern.Prefix: "-gnatw.N"
   ]
   rationale    = '''
     Enabling the warning would interfere with the use of Atomic
     variables, which some lower-level software needs to use
   '''
}

// from compiler_warning_optional.csv, row 8
Compiler_Switch_Constraint Compiler_Switch_Warning_Lowercaseo {
   warn_related = true
   status       = Status.Allowed
   switches     = [
     Pattern.Prefix: "-gnatwo"
   ]
   rationale    = '''
     Warnings enabled by this switch are enabled by default
   '''
}

// from compiler_warning_optional.csv, row 9
Compiler_Switch_Constraint Compiler_Switch_Group_8 {
   warn_related = true
   status       = Status.Allowed
   switches     = [
     Pattern.Prefix: "-gnatw.q",
     Pattern.Prefix: "-gnatw.Q"
   ]
   rationale    = '''
     Warnings enabled by this switch concern performance and space
     efficiency but not code correctness.
   '''
}

// from compiler_warning_optional.csv, row 10
Compiler_Switch_Constraint Compiler_Switch_Group_9 {
   warn_related = true
   status       = Status.Allowed
   switches     = [
     Pattern.Prefix: "-gnatw.u",
     Pattern.Prefix: "-gnatw.U"
   ]
   rationale    = '''
     Using comparisons of enumerated values is a common idiom for
     determining whether a given enumerated value is within a certain
     range of enumerated values. It should not be required that this
     be explicitly allowed in the definition of the enumerated type.
   '''
}

// from compiler_warning_optional.csv, row 11
Compiler_Switch_Constraint Compiler_Switch_Group_10 {
   warn_related = true
   status       = Status.Allowed
   switches     = [
     Pattern.Prefix: "-gnatw.y",
     Pattern.Prefix: "-gnatw.Y"
   ]
   rationale    = '''
     This switch controls verbose informational messages that
     typically do not indicate errors
   '''
}

// from compiler_warning_optional.csv, row 12
Compiler_Switch_Constraint Compiler_Switch_Group_11 {
   warn_related = true
   status       = Status.Allowed
   switches     = [
     Pattern.Prefix: "-Wunused",
     Pattern.Prefix: "-Wuninitialized"
   ]
   rationale    = '''
     Entities that are declared but not referenced, or uninitialized,
     from a back end perspective but not from a front end perspective
     are more likely to be indicative of the effects of optimizations
     than real errors
   '''
}

// from compiler_warning_required.csv, row 1
Compiler_Switch_Constraint Compiler_Switch_Group_12 {
   warn_related = true
   status       = Status.Required
   switches     = [
     Pattern.Prefix: "-gnatwa",
     Pattern.Prefix: "-Wall"
   ]
   rationale    = '''
     Enables warnings that are not "controversial". Note: The use of
     -Wall includes all the effects of ``-gnatwa``, but this process
     requires both options so as to be explicit.
   '''
}

// from compiler_warning_required.csv, row 2
Compiler_Switch_Constraint Compiler_Switch_Warning_Lowercase_Dot_d {
   warn_related = true
   status       = Status.Required
   switches     = [
     Pattern.Prefix: "-gnatw.d"
   ]
   rationale    = '''
     Expected to provide greater clarity to warnings. (Also, other
     compilers do this by default.)
   '''
}

// from compiler_warning_required.csv, row 3
Compiler_Switch_Constraint Compiler_Switch_Group_13 {
   warn_related = true
   status       = Status.Required
   switches     = [
     Pattern.Prefix: "-gnatwe",
     Pattern.Prefix: "-Werror"
   ]
   rationale    = '''
     Treating warnings as errors results in warnings being taken
     seriously and results in cleaner build output Note: The use of
     -Werror includes all the effects of ``-gnatwe``, but this process
     requires both options so as to be explicit.
   '''
}

// from compiler_warning_required.csv, row 4
Compiler_Switch_Constraint Compiler_Switch_Warning_Lowercaseh {
   warn_related = true
   status       = Status.Required
   switches     = [
     Pattern.Prefix: "-gnatwh"
   ]
   rationale    = '''
     Implicitly-hidden declarations are a potential source of
     confusion when reading code. Note: The Ada/SPARK Guidelines
     document is expected to provide guidance on how to mitigate the
     risk that adding a declaration to a package will cause another
     package to fail to compile due to warnings enabled by
     ``-gnatwh``.
   '''
}

// from compiler_warning_required.csv, row 5
Compiler_Switch_Constraint Compiler_Switch_Warning_Lowercase_Dot_h {
   warn_related = true
   status       = Status.Required
   switches     = [
     Pattern.Prefix: "-gnatw.h"
   ]
   rationale    = '''
     Record representation clauses should be complete and fully
     specify the layout, and that a hole might be an indication of an
     error.
   '''
}

// from compiler_warning_required.csv, row 6
Compiler_Switch_Constraint Compiler_Switch_Warning_Lowercase_Dot_j {
   warn_related = true
   status       = Status.Required
   switches     = [
     Pattern.Prefix: "-gnatw.j"
   ]
   rationale    = '''
     Per AdaCore (see :gt:`V413-003`), the chief designer of Ada 95
     believes that Ada "should have disallowed ... adding visible
     operations to a tagged type after deriving a private extension
     from it" due to the confusion created. The capability also does
     not appear to add value to the language.
   '''
}

// from compiler_warning_required.csv, row 7
Compiler_Switch_Constraint Compiler_Switch_Warning_Lowercase_Dot_k {
   warn_related = true
   status       = Status.Required
   switches     = [
     Pattern.Prefix: "-gnatw.k"
   ]
   rationale    = '''
     As warned by AdaCore, redefining names in package Standard could
     lead to confusion.
   '''
}

// from compiler_warning_required.csv, row 8
Compiler_Switch_Constraint Compiler_Switch_Warning_Lowercasel {
   warn_related = true
   status       = Status.Required
   switches     = [
     Pattern.Prefix: "-gnatwl"
   ]
   rationale    = '''
     This warning appears to prevent elaboration problems that could
     lead to exceptions
   '''
}

// from compiler_warning_required.csv, row 9
Compiler_Switch_Constraint Compiler_Switch_Warning_Lowercase_Dot_o {
   warn_related = true
   status       = Status.Required
   switches     = [
     Pattern.Prefix: "-gnatw.o"
   ]
   rationale    = '''
     This switch enables warnings that are a straightforward extension
     of warnings enabled by ``-gnatwu``/``-gnatwa``. For consistency,
     enable these warnings.
   '''
}

// from compiler_warning_required.csv, row 10
Compiler_Switch_Constraint Compiler_Switch_Warning_Lowercase_Underscore_r {
   warn_related = true
   status       = Status.Required
   switches     = [
     Pattern.Prefix: "-gnatw_r"
   ]
   rationale    = '''
     Record representation clauses should be structurally consistent
     with the associated record type definitions to ensure a complete
     consideration of the constraints on representation.
   '''
}

// from compiler_warning_required.csv, row 11
Compiler_Switch_Constraint Compiler_Switch_Warning_Lowercase_Dot_s {
   warn_related = true
   status       = Status.Required
   switches     = [
     Pattern.Prefix: "-gnatw.s"
   ]
   rationale    = '''
     Record representation clauses should not contradict the
     associated record type definitions.
   '''
}

// from compiler_warning_required.csv, row 12
Compiler_Switch_Constraint Compiler_Switch_Warning_Lowercaset {
   warn_related = true
   status       = Status.Required
   switches     = [
     Pattern.Prefix: "-gnatwt"
   ]
   rationale    = '''
     It is expected that every code path within a compilation unit
     will be reachable without modification of the compilation unit so
     that every code path can be tested using the same object code as
     what ships to customers
   '''
}

// from compiler_warning_required.csv, row 13
Compiler_Switch_Constraint Compiler_Switch_Warning_Lowercase_Dot_w {
   warn_related = true
   status       = Status.Required
   switches     = [
     Pattern.Prefix: "-gnatw.w"
   ]
   rationale    = '''
     Enables useful warnings about misuse of Warnings Off pragmas.
   '''
}

// from compiler_warning_required.csv, row 14
Compiler_Switch_Constraint Compiler_Switch_Warning_Uppercase_Dot_X {
   warn_related = true
   status       = Status.Required
   switches     = [
     Pattern.Prefix: "-gnatw.X"
   ]
   rationale    = '''
     Necessary when using pragma Restrictions
     (No_Exception_Propagation) to avoid spurious warnings compiling
     SPARK code (see :gt:`V223-002`)
   '''
}

// from gnatcheck_banned.csv, row 1
Switch_Constraint Check_Switch_brief {
   tool         = Tool.GNAT_Check
   status       = Status.Banned
   switches     = [
     Pattern.Prefix: "--brief"
   ]
   rationale    = '''
     Potentially suppresses reporting of rule violations on stdout /
     stderr.
   '''
}

// from gnatcheck_banned.csv, row 2
Switch_Constraint Check_Switch_charset {
   tool         = Tool.GNAT_Check
   status       = Status.Banned
   switches     = [
     Pattern.Prefix: "--charset=<charset>"
   ]
   rationale    = '''
     Potentially results in misinterpretation of files using the
     default character set.
   '''
}

// from gnatcheck_banned.csv, row 3
Switch_Constraint Check_Switch_help {
   tool         = Tool.GNAT_Check
   status       = Status.Banned
   switches     = [
     Pattern.Prefix: "--help"
   ]
   rationale    = '''
     Causes GNATcheck to exit without checking for violations of any
     of the specified rules.
   '''
}

// from gnatcheck_banned.csv, row 4
Switch_Constraint Check_Switch_ignore {
   tool         = Tool.GNAT_Check
   status       = Status.Banned
   switches     = [
     Pattern.Prefix: "--ignore=<filename>"
   ]
   rationale    = '''
     Can cause ADS/ADB files in the project specified with -P to be
     ignored.
   '''
}

// from gnatcheck_banned.csv, row 5
Switch_Constraint Check_Switch_ignore_project_switches {
   tool         = Tool.GNAT_Check
   status       = Status.Banned
   switches     = [
     Pattern.Prefix: "--ignore-project-switches"
   ]
   rationale    = '''
     Would cause GNATcheck to ignore mandatory switches specified via
     the Check project in the project file.
   '''
}

// from gnatcheck_banned.csv, row 6
Switch_Constraint Check_Switch_RTS {
   tool         = Tool.GNAT_Check
   status       = Status.Banned
   switches     = [
     Pattern.Prefix: "--RTS"
   ]
   rationale    = '''
     Per the :ref:`Create_Project_File <step-create-project-file>`
     step, a safety-qualified runtime is already specified in the
     project file using the Runtime("Ada") attribute. This ensures the
     various tools use a consistent runtime.
   '''
}

// from gnatcheck_banned.csv, row 7
Switch_Constraint Check_Switch_simple_project {
   tool         = Tool.GNAT_Check
   status       = Status.Banned
   switches     = [
     Pattern.Prefix: "--simple-project"
   ]
   rationale    = '''
     It is not clear from the GNATcheck documentation whether this
     switch might cause some files in the project to be ignored by
     GNATcheck.
   '''
}

// from gnatcheck_banned.csv, row 8
Switch_Constraint Check_Switch_target {
   tool         = Tool.GNAT_Check
   status       = Status.Banned
   switches     = [
     Pattern.Prefix: "--target=<targetname>"
   ]
   rationale    = '''
     Per the :ref:`Create_Project_File <step-create-project-file>`
     step, the target is already specified in the project file using
     the Target attribute. This ensures the various tools use a
     consistent target configuration.
   '''
}

// from gnatcheck_banned.csv, row 9
Switch_Constraint Check_Switch_version {
   tool         = Tool.GNAT_Check
   status       = Status.Banned
   switches     = [
     Pattern.Prefix: "--version"
   ]
   rationale    = '''
     Causes GNATcheck to exit without checking for violations of any
     of the specified rules.
   '''
}

// from gnatcheck_banned.csv, row 10
Switch_Constraint Check_Switch_files {
   tool         = Tool.GNAT_Check
   status       = Status.Banned
   switches     = [
     Pattern.Prefix: "-files=<filename>"
   ]
   rationale    = '''
     Can cause ADS/ADB files in the project specified with -P to be
     ignored.
   '''
}

// from gnatcheck_banned.csv, row 11
Switch_Constraint Check_Switch_q {
   tool         = Tool.GNAT_Check
   status       = Status.Banned
   switches     = [
     Pattern.Prefix: "-q"
   ]
   rationale    = '''
     Potentially suppresses reporting of rule violations on stdout /
     stderr.
   '''
}

// from gnatcheck_optional.csv, row 1
Switch_Constraint Check_Switch_check_semantic {
   tool         = Tool.GNAT_Check
   status       = Status.Allowed
   switches     = [
     Pattern.Prefix: "--check-semantic"
   ]
   rationale    = '''
     The compiler will detect the same errors.
   '''
}

// from gnatcheck_optional.csv, row 2
Switch_Constraint Check_Switch_include_file {
   tool         = Tool.GNAT_Check
   status       = Status.Allowed
   switches     = [
     Pattern.Prefix: "--include-file=<file>"
   ]
   rationale    = '''
     Has no effect on reporting of rule violations on stdout / stderr.
   '''
}

// from gnatcheck_optional.csv, row 3
Switch_Constraint Check_Switch_no_objects_dir {
   tool         = Tool.GNAT_Check
   status       = Status.Allowed
   switches     = [
     Pattern.Prefix: "--no-objects-dir"
   ]
   rationale    = '''
     The GNATcheck output files are not significant to this process,
     since the existence of rule violations is reported on the command
     line.
   '''
}

// from gnatcheck_optional.csv, row 4
Switch_Constraint Check_Switch_no_subprojects {
   tool         = Tool.GNAT_Check
   status       = Status.Allowed
   switches     = [
     Pattern.Prefix: "--no-subprojects"
   ]
   rationale    = '''
     This switch does not control the processing of ADS/ADB files from
     the project specified with -P (the "argument project"). This
     switch only controls the processing of ADS/ADB files from other
     projects recursively included in the argument project.
   '''
}

// from gnatcheck_optional.csv, row 5
Switch_Constraint Check_Switch_rules_dir {
   tool         = Tool.GNAT_Check
   status       = Status.Allowed
   switches     = [
     Pattern.Prefix: "--rules-dir=<dir>"
   ]
   rationale    = '''
     This is a valid way to specify the locations of custom rules.
   '''
}

// from gnatcheck_optional.csv, row 6
Switch_Constraint Check_Switch_show {
   tool         = Tool.GNAT_Check
   status       = Status.Allowed
   switches     = [
     Pattern.Prefix: "--show=rule"
   ]
   rationale    = '''
     Has no effect on whether the number of rule violations reported
     on stdout / stderr is zero or non-zero.
   '''
}

// from gnatcheck_optional.csv, row 7
Switch_Constraint Check_Switch_subdirs {
   tool         = Tool.GNAT_Check
   status       = Status.Allowed
   switches     = [
     Pattern.Prefix: "--subdirs=<dir>"
   ]
   rationale    = '''
     The GNATcheck output files are not significant to this process,
     since the existence of rule violations is reported on the command
     line.
   '''
}

// from gnatcheck_optional.csv, row 8
Switch_Constraint Check_Switch_eL {
   tool         = Tool.GNAT_Check
   status       = Status.Allowed
   switches     = [
     Pattern.Prefix: "-eL"
   ]
   rationale    = '''
     The usage of symbol links to access projects is out of the scope
     of this process.
   '''
}

// from gnatcheck_optional.csv, row 9
Switch_Constraint Check_Switch_from {
   tool         = Tool.GNAT_Check
   status       = Status.Allowed
   switches     = [
     Pattern.Prefix: "-from=<rule_option_filename>"
   ]
   rationale    = '''
     This is a valid way to enable rules, but +R<rule> can be used
     instead.
   '''
}

// from gnatcheck_optional.csv, row 10
Switch_Constraint Check_Switch_h {
   tool         = Tool.GNAT_Check
   status       = Status.Allowed
   switches     = [
     Pattern.Prefix: "-h"
   ]
   rationale    = '''
     Has no effect on reporting of rule violations.
   '''
}

// from gnatcheck_optional.csv, row 11
Switch_Constraint Check_Switch_j {
   tool         = Tool.GNAT_Check
   status       = Status.Allowed
   switches     = [
     Pattern.Prefix: "-j"
   ]
   rationale    = '''
     Has no effect on reporting of rule violations.
   '''
}

// from gnatcheck_optional.csv, row 12
Switch_Constraint Check_Switch_l {
   tool         = Tool.GNAT_Check
   status       = Status.Allowed
   switches     = [
     Pattern.Prefix: "-l"
   ]
   rationale    = '''
     Has no effect on reporting of rule violations on stdout / stderr.
   '''
}

// from gnatcheck_optional.csv, row 13
Switch_Constraint Check_Switch_log {
   tool         = Tool.GNAT_Check
   status       = Status.Allowed
   switches     = [
     Pattern.Prefix: "-log"
   ]
   rationale    = '''
     Has no effect on reporting of rule violations on stdout / stderr.
   '''
}

// from gnatcheck_optional.csv, row 14
Switch_Constraint Check_Switch_m {
   tool         = Tool.GNAT_Check
   status       = Status.Allowed
   switches     = [
     // <number>
     Pattern.Prefix: "-m"
   ]
   rationale    = '''
     Has no effect on whether the number of rule violations reported
     on stdout / stderr is zero or non-zero.
   '''
}

// from gnatcheck_optional.csv, row 15
Switch_Constraint Check_Switch_nt {
   tool         = Tool.GNAT_Check
   status       = Status.Allowed
   switches     = [
     Pattern.Prefix: "-nt"
   ]
   rationale    = '''
     Has no effect on reporting of rule violations on stdout / stderr.
   '''
}

// from gnatcheck_optional.csv, row 16
Switch_Constraint Check_Switch_o {
   tool         = Tool.GNAT_Check
   status       = Status.Allowed
   switches     = [
     // <report_file>
     Pattern.Prefix: "-o"
   ]
   rationale    = '''
     Has no effect on reporting of rule violations on stdout / stderr.
   '''
}

// from gnatcheck_optional.csv, row 17
Switch_Constraint Check_Switch_ox {
   tool         = Tool.GNAT_Check
   status       = Status.Allowed
   switches     = [
     // <report_file>
     Pattern.Prefix: "-ox"
   ]
   rationale    = '''
     Has no effect on reporting of rule violations on stdout / stderr.
   '''
}

// from gnatcheck_optional.csv, row 18
Switch_Constraint Check_Switch_Plus_Rrule {
   tool         = Tool.GNAT_Check
   status       = Status.Allowed
   switches     = [
     Pattern.Prefix: "+R<rule>"
   ]
   rationale    = '''
     This is a valid way to enable rules, but
     -from=<rule_option_filename> can be used instead.
   '''
}

// from gnatcheck_optional.csv, row 19
Switch_Constraint Check_Switch_Rrule {
   tool         = Tool.GNAT_Check
   status       = Status.Allowed
   switches     = [
     Pattern.Prefix: "-R<rule>"
   ]
   rationale    = '''
     This can disable rules that are required to be enabled. All rules
     are disabled by default, so there is never a need to explicitly
     disable rules (undesired rules should simply not be enabled in
     the first place).
   '''
}

// from gnatcheck_optional.csv, row 20
Switch_Constraint Check_Switch_s {
   tool         = Tool.GNAT_Check
   status       = Status.Allowed
   switches     = [
     Pattern.Prefix: "-s"
   ]
   rationale    = '''
     Has no effect on reporting of rule violations on stdout / stderr.
   '''
}

// from gnatcheck_optional.csv, row 21
Switch_Constraint Check_Switch_t {
   tool         = Tool.GNAT_Check
   status       = Status.Allowed
   switches     = [
     Pattern.Prefix: "-t"
   ]
   rationale    = '''
     Has no effect on reporting of rule violations on stdout / stderr.
   '''
}

// from gnatcheck_optional.csv, row 22
Switch_Constraint Check_Switch_v {
   tool         = Tool.GNAT_Check
   status       = Status.Allowed
   switches     = [
     Pattern.Prefix: "-v"
   ]
   rationale    = '''
     Has no effect on reporting of rule violations on stdout / stderr.
   '''
}

// from gnatcheck_optional.csv, row 23
Switch_Constraint Check_Switch_xml {
   tool         = Tool.GNAT_Check
   status       = Status.Allowed
   switches     = [
     Pattern.Prefix: "-xml"
   ]
   rationale    = '''
     Has no effect on reporting of rule violations on stdout / stderr.
   '''
}

// from gnatcheck_optional.csv, row 24
Switch_Constraint Check_Switch_Xname {
   tool         = Tool.GNAT_Check
   status       = Status.Allowed
   switches     = [
     Pattern.Prefix: "-Xname=value"
   ]
   rationale    = '''
     Configuration data is allowed.
   '''
}

// from gnatcheck_required.csv, row 1
Switch_Constraint Check_Switch_check_redefinition {
   tool         = Tool.GNAT_Check
   status       = Status.Required
   switches     = [
     Pattern.Prefix: "--check-redefinition"
   ]
   rationale    = '''
     Detects errors in rule set that could cause unexpected
     suppression of rules.
   '''
}

// from gnatcheck_required.csv, row 2
Switch_Constraint Check_Switch_Group_1 {
   tool         = Tool.GNAT_Check
   status       = Status.Required
   switches     = [
     // *or*
     Pattern.Prefix: "-from=<rule_option_filename>",
     Pattern.Prefix: "+R<rule>"
   ]
   rationale    = '''
     One of these options must be used to enable the rules required in
     the Table of Required GNATcheck Rules. Note: Entries of the form
     -R<rule> must not exist in any rule option file specified via
     -from=<rule_option_filename>, whether specified on the command
     line or inside another rule option file.
   '''
}

// from gnatcheck_required.csv, row 3
Switch_Constraint Check_Switch_P {
   tool         = Tool.GNAT_Check
   status       = Status.Required
   switches     = [
     // <project-file.gpr>
     Pattern.Prefix: "-P"
   ]
   rationale    = '''
     The use of -P ensures that switches passed via the Check package
     of the project file are effective.
   '''
}

// from gnatcheck_required.csv, row 4
Switch_Constraint Check_Switch_U {
   tool         = Tool.GNAT_Check
   status       = Status.Required
   switches     = [
     Pattern.Prefix: "-U"
   ]
   rationale    = '''
     Without -U, GNATcheck will not necessarily analyze all the units
     that are part of the project.
   '''
}

// from gnatcheck_required_rules.csv, row 1
Rule_Constraint Check_Rule_Ada_2022_In_Ghost_Code {
   status       = Status.Required
   rule = "Ada_2022_In_Ghost_Code"
   rationale    = '''
     Required to flag Ada 2022 code used outside of contracts, which
     would violate the GNAT safety manual (see step
     Manual_Check_Against_Safety_Manuals)
   '''
}

// from gnatcheck_required_rules.csv, row 2
Rule_Constraint Check_Rule_Forbidden_Attributes_Initialized {
   status       = Status.Required
   rule = "Forbidden_Attributes:Initialized"
   rationale    = '''
     Needed to identify cases where manual review is required for
     GNATprove assumption [SPARK_INITIALIZED_ATTRIBUTE]
   '''
}

// from gnatcheck_required_rules.csv, row 3
Rule_Constraint Check_Rule_Forbidden_Pragmas_Validity_Checks {
   status       = Status.Required
   rule = "Forbidden_Pragmas:Validity_Checks"
   rationale    = '''
     Required because pragma Validity_Checks is not safety-certified
   '''
}

// from gnatcheck_required_rules.csv, row 4
Rule_Constraint Check_Rule_Forbidden_Pragmas_Assertion_Policy {
   status       = Status.Required
   rule = "Forbidden_Pragmas:Assertion_Policy"
   rationale    = '''
     Required to avoid inclusion of Ada 2022 code in contracts into
     the production build, which would violate the GNAT safety manual
     (see step Manual_Check_Against_Safety_Manuals) Note: With a
     GNATcheck diagnostic justification annotation, pragma
     Assertion_Policy can still be used with the Ignore parameter as
     long as additional tests are specified; see the :ref:`Write_Tests
     <step-write-tests>` step). However, pragma Assertion_Policy with
     the Check parameter is only valid if it is known that all
     applicable contracts entirely refrain from using Ada 2022
     features.
   '''
}

// from gnatcheck_required_rules.csv, row 5
Rule_Constraint Check_Rule_Forbidden_Pragmas_Ignore_Pragma {
   status       = Status.Required
   rule = "Forbidden_Pragmas:Ignore_Pragma"
   rationale    = '''
     Required because pragma Ignore_Pragma can cause SPARK to be
     silently disabled.
   '''
}

// from gnatcheck_required_rules.csv, row 6
Rule_Constraint Check_Rule_Metrics_Cyclomatic_Complexity_10 {
   status       = Status.Required
   // (to be enforced on non-proven code only)
   rule = "Metrics_Cyclomatic_Complexity:10"
   rationale    = '''
     Required for non-proven code (code that is not SPARK_Mode => On
     and code that is annotated with Skip_Proof or
     Skip_Flow_And_Proof) for compliance with ISO 26262-6:2018, Table
     1 row 1a "Enforcement of low complexity" and 8.4.5d "simplicity".
     Note: This process does not enforce McCabe cyclomatic complexity
     limits on proven SPARK executable bodies because it is neither
     effective for reducing risk nor necessary for compliance with ISO
     26262. * The enforcement of low complexity in proven SPARK code
     is not effective for reducing risk because (1) the use of
     GNATprove on SPARK executable bodies significantly reduces the
     risk of complexity-induced systematic faults, (2) complexity
     metrics are a poor metric for comprehensibility, and (3)
     comprehensibility is already verified in the
     :ref:`Inspect_Implementation <step-inspect-implementation>` step.
     * The enforcement of low complexity in proven SPARK code is not
     necessary for compliance with ISO 26262 because the
     recommendation to enforce low complexity in programming languages
     is given in ISO 26262-6:2018, 5.4.3 in the context of mitigating
     programming language deficiencies relative to the criteria
     specified in ISO 26262-6:2018, 5.4.2, which SPARK largely excels
     at. Moreover, the aforementioned recommendation is accompanied by
     a footnote acknowledging "an appropriate compromise of this topic
     with other requirements of this document may be required" (ISO
     26262-6:2018, Table 1, footnote a), and it is frequently the case
     that compliance with cyclomatic complexity limits actually
     reduces the comprehensibility of code (e.g., obfuscation of
     algorithms through refactoring into smaller subprograms). Note:
     AdaCore recommends scrutinizing executable bodies with McCabe
     cyclomatic complexities greater than 10 because this is the
     practice AdaCore uses for its own certified Ada runtime
     libraries.
   '''
}

// from gnatcheck_required_rules.csv, row 7
Rule_Constraint Check_Rule_Procedures_Without_Globals {
   status       = Status.Required
   rule = "Procedures_Without_Globals"
   rationale    = '''
     Required to flag SPARK procedure declarations with no Global
     aspect (see note in :ref:`Capture_Requirements
     <step-capture-requirements>` step)
   '''
}

// from gnatcheck_required_rules.csv, row 8
Rule_Constraint Check_Rule_Restrictions_Max_Protected_Entries_0 {
   status       = Status.Required
   rule = "Restrictions:Max_Protected_Entries=>0"
   rationale    = '''
     Needed to identify cases where manual review is necessary for
     GNATprove assumption [SPARK_OVERRIDING_AND_TASKING]
   '''
}

// from gnatcheck_required_rules.csv, row 9
Rule_Constraint Check_Rule_Restrictions_No_Floating_Point {
   status       = Status.Required
   rule = "Restrictions:No_Floating_Point"
   rationale    = '''
     Needed to identify cases where manual review is necessary for
     GNATprove assumption [SPARK_FLOATING_POINT]
   '''
}

// from gnatcheck_required_rules.csv, row 10
Rule_Constraint Check_Rule_Restrictions_No_Protected_Types {
   status       = Status.Required
   rule = "Restrictions:No_Protected_Types"
   rationale    = '''
     Needed to identify cases where manual review is necessary for
     GNATprove assumption [SPARK_OVERRIDING_AND_TASKING]
   '''
}

// from gnatcheck_required_rules.csv, row 11
Rule_Constraint Check_Rule_Restrictions_No_Specification_Of_Aspect_Iterable {
   status       = Status.Required
   rule = "Restrictions:No_Specification_Of_Aspect=>Iterable"
   rationale    = '''
     Needed to identify cases where manual review is necessary for
     GNATprove assumptions [SPARK_ITERABLE] and
     [SPARK_ITERABLE_FOR_PROOF]
   '''
}

// from gnatcheck_required_rules.csv, row 12
Rule_Constraint Check_Rule_Restrictions_No_Use_Of_Entity_Ada_Dot_Task_Identification_Dot_Current_Task {
   status       = Status.Required
   rule = "Restrictions:No_Use_Of_Entity=>Ada.Task_Identification.Current_Task"
   rationale    = '''
     Needed to identify cases where manual review is necessary for
     [SPARK_OVERRIDING_AND_TASKING]
   '''
}

// from gnatcheck_required_rules.csv, row 13
Rule_Constraint Check_Rule_Restrictions_No_Use_Of_Entity_Synchronous_Task_Control {
   status       = Status.Required
   rule = "Restrictions:No_Use_Of_Entity=>Synchronous_Task_Control"
   rationale    = '''
     Needed to identify cases where manual review is necessary for
     [SPARK_OVERRIDING_AND_TASKING]
   '''
}

// from gnatcheck_required_rules.csv, row 14
Rule_Constraint Check_Rule_Goto_Statements_Only_Unconditional {
   status       = Status.Required
   rule = "Goto_Statements:Only_Unconditional"
   rationale    = '''
     Required for compliance with ISO 26262-6:2018, Table 6, row 1i
     "No unconditional jumps"
   '''
}

// from gnatprove_banned.csv, row 1
Switch_Constraint SPARK_Switch_assumptions {
   tool         = Tool.SPARK
   status       = Status.Banned
   switches     = [
     Pattern.Prefix: "--assumptions"
   ]
   rationale    = '''
     This switch is not safety-qualified.
   '''
}

// from gnatprove_banned.csv, row 2
Switch_Constraint SPARK_Switch_clean {
   tool         = Tool.SPARK
   status       = Status.Banned
   switches     = [
     Pattern.Prefix: "--clean"
   ]
   rationale    = '''
     This switch directs GNATprove not to attempt to prove anything.
     NOTE: This switch is required, not prohibited, during the
     cleaning part of the :ref:`Verify_Project <step-verify-project>`
     step.
   '''
}

// from gnatprove_banned.csv, row 3
Switch_Constraint SPARK_Switch_cwe {
   tool         = Tool.SPARK
   status       = Status.Banned
   switches     = [
     Pattern.Prefix: "--cwe"
   ]
   rationale    = '''
     This switch is not safety-qualified.
   '''
}

// from gnatprove_banned.csv, row 4
Switch_Constraint SPARK_Switch_Group_1 {
   tool         = Tool.SPARK
   status       = Status.Banned
   switches     = [
     Pattern.Prefix: "--help",
     Pattern.Prefix: "-h"
   ]
   rationale    = '''
     This switch is not safety-qualified.
   '''
}

// from gnatprove_banned.csv, row 5
Switch_Constraint SPARK_Switch_list_categories {
   tool         = Tool.SPARK
   status       = Status.Banned
   switches     = [
     Pattern.Prefix: "--list-categories"
   ]
   rationale    = '''
     This switch prevents GNATprove from fulfilling its intended
     function. This switch is also not safety-qualified.
   '''
}

// from gnatprove_banned.csv, row 6
Switch_Constraint SPARK_Switch_Group_2 {
   tool         = Tool.SPARK
   status       = Status.Banned
   switches     = [
     Pattern.Prefix: "--mode=bronze",
     Pattern.Prefix: "--mode=check",
     Pattern.Prefix: "--mode=check_all",
     Pattern.Prefix: "--mode=flow",
     Pattern.Prefix: "--mode=prove",
     Pattern.Prefix: "--mode=stone"
   ]
   rationale    = '''
     --mode=check would partially disable checks that SPARK_Mode => On
     packages and subprograms are within the SPARK subset of Ada.
     --mode=check, --mode=check_all, --mode=prove, and --mode=stone
     would partially or fully disable flow analysis, which is needed
     to verify initialization of variables before use and compliance
     with some contracts. --mode=flow and --mode=bronze would disable
     verification of functional contracts and of the absence of
     run-time errors. These switches are also not safety-qualified.
   '''
}

// from gnatprove_banned.csv, row 7
Switch_Constraint SPARK_Switch_Group_3 {
   tool         = Tool.SPARK
   status       = Status.Banned
   switches     = [
     Pattern.Prefix: "--mode=gold",
     Pattern.Prefix: "--mode=silver"
   ]
   rationale    = '''
     Though these switches are equivalent to --mode=all, they are not
     safety-qualified (where --mode=all is safety-qualified).
   '''
}

// from gnatprove_banned.csv, row 8
Switch_Constraint SPARK_Switch_Group_4 {
   tool         = Tool.SPARK
   status       = Status.Banned
   switches     = [
     Pattern.Prefix: "--limit-line=...",
     Pattern.Prefix: "--limit-region=...",
     Pattern.Prefix: "--limit-subp=...",
     Pattern.Prefix: "--no-subprojects"
   ]
   rationale    = '''
     With any of these options, GNATprove will not necessarily analyze
     all of the code within each analyzed unit. These switches are
     also not safety-qualified.
   '''
}

// from gnatprove_banned.csv, row 9
Switch_Constraint SPARK_Switch_output_msg_only {
   tool         = Tool.SPARK
   status       = Status.Banned
   switches     = [
     Pattern.Prefix: "--output-msg-only"
   ]
   rationale    = '''
     This switch is not safety-qualified.
   '''
}

// from gnatprove_banned.csv, row 10
Switch_Constraint SPARK_Switch_proof {
   tool         = Tool.SPARK
   status       = Status.Banned
   switches     = [
     Pattern.Prefix: "--proof"
   ]
   rationale    = '''
     This switch is not safety-qualified.
   '''
}

// from gnatprove_banned.csv, row 11
Switch_Constraint SPARK_Switch_Banned_Provers {
   tool         = Tool.SPARK
   status       = Status.Banned
   switches     = [
     // (or any superset of this)
     Pattern.Prefix: "--prover=colibri"
   ]
   rationale    = '''
     GNATprove's use of the Colibri prover is not safety-qualified.
   '''
}

// from gnatprove_banned.csv, row 12
Switch_Constraint SPARK_Switch_replay {
   tool         = Tool.SPARK
   status       = Status.Banned
   switches     = [
     Pattern.Prefix: "--replay"
   ]
   rationale    = '''
     This switch is not safety-qualified.
   '''
}

// from gnatprove_banned.csv, row 13
Switch_Constraint SPARK_Switch_RTS {
   tool         = Tool.SPARK
   status       = Status.Banned
   switches     = [
     Pattern.Prefix: "--RTS=<dir>"
   ]
   rationale    = '''
     Per the :ref:`Create_Project_File <step-create-project-file>`
     step, a safety-qualified runtime is already specified in the
     project file using the Runtime("Ada") attribute. This ensures the
     various tools use a consistent runtime.
   '''
}

// from gnatprove_banned.csv, row 14
Switch_Constraint SPARK_Switch_subdirs {
   tool         = Tool.SPARK
   status       = Status.Banned
   switches     = [
     Pattern.Prefix: "--subdirs=..."
   ]
   rationale    = '''
     This switch is not safety-qualified.
   '''
}

// from gnatprove_banned.csv, row 15
Switch_Constraint SPARK_Switch_version {
   tool         = Tool.SPARK
   status       = Status.Banned
   switches     = [
     Pattern.Prefix: "--version"
   ]
   rationale    = '''
     This switch prevents GNATprove from fulfilling its intended
     function. This switch is also not safety-qualified.
   '''
}

// from gnatprove_banned.csv, row 16
Switch_Constraint SPARK_Switch_Group_5 {
   tool         = Tool.SPARK
   status       = Status.Banned
   switches     = [
     Pattern.Prefix: "--warnings=off",
     Pattern.Prefix: "--warnings=continue"
   ]
   rationale    = '''
     This switch would interfere with the effect of -warnings=error.
     These switches are also not safety-qualified.
   '''
}

// from gnatprove_banned.csv, row 17
Switch_Constraint SPARK_Switch_aP {
   tool         = Tool.SPARK
   status       = Status.Banned
   switches     = [
     Pattern.Prefix: "-aP=..."
   ]
   rationale    = '''
     This switch is not safety-qualified.
   '''
}

// from gnatprove_banned.csv, row 18
Switch_Constraint SPARK_Switch_f {
   tool         = Tool.SPARK
   status       = Status.Banned
   switches     = [
     Pattern.Prefix: "-f"
   ]
   rationale    = '''
     This switch is not safety-qualified. Note that this switch is not
     needed to ensure correct results.
   '''
}

// from gnatprove_banned.csv, row 19
Switch_Constraint SPARK_Switch_gnateT {
   tool         = Tool.SPARK
   status       = Status.Banned
   switches     = [
     Pattern.Prefix: "-gnateT=<target.atp>"
   ]
   rationale    = '''
     This switch could result in an inconsistency between the target
     configuration used by the compiler and the target configuration
     used by GNATprove.
   '''
}

// from gnatprove_banned.csv, row 20
Switch_Constraint SPARK_Switch_k {
   tool         = Tool.SPARK
   status       = Status.Banned
   switches     = [
     Pattern.Prefix: "-k"
   ]
   rationale    = '''
     This switch is not safety-qualified.
   '''
}

// from gnatprove_banned.csv, row 21
Switch_Constraint SPARK_Switch_m {
   tool         = Tool.SPARK
   status       = Status.Banned
   switches     = [
     Pattern.Prefix: "-m"
   ]
   rationale    = '''
     This switch is not safety-qualified.
   '''
}

// from gnatprove_banned.csv, row 22
Switch_Constraint SPARK_Switch_q {
   tool         = Tool.SPARK
   status       = Status.Banned
   switches     = [
     Pattern.Prefix: "-q"
   ]
   rationale    = '''
     This switch is not safety-qualified. (Note however that a
     synonym, --quiet, is safety-qualified.)
   '''
}

// from gnatprove_banned.csv, row 23
Switch_Constraint SPARK_Switch_Lowercase_U {
   tool         = Tool.SPARK
   status       = Status.Banned
   switches     = [
     Pattern.Prefix: "-u"
   ]
   rationale    = '''
     Would conflict with -U. This switch is also not safety-qualified.
   '''
}

// from gnatprove_banned.csv, row 24
Switch_Constraint SPARK_Switch_v {
   tool         = Tool.SPARK
   status       = Status.Banned
   switches     = [
     Pattern.Prefix: "-v"
   ]
   rationale    = '''
     This switch is not safety-qualified. (Note however that a
     synonym, --verbose, is safety-qualified.)
   '''
}

// from gnatprove_banned.csv, row 25
Switch_Constraint SPARK_Switch_All {
   tool         = Tool.SPARK
   status       = Status.Banned
   switches     = [
     // switches not covered in this section
     Pattern.Prefix: "All"
   ]
   rationale    = '''
     These switches are not safety-qualified.
   '''
}

// from gnatprove_optional.csv, row 1
Switch_Constraint SPARK_Switch_counterexamples {
   tool         = Tool.SPARK
   status       = Status.Allowed
   switches     = [
     Pattern.Prefix: "--counterexamples"
   ]
   rationale    = '''
     Though this switch is not safety-qualified with the on setting,
     its use is nevertheless permitted because this switch cannot lead
     to false negatives in verification results. In a worst-case
     scenario, verification does not complete successfully and a
     faulty counterexample is provided that does not explain the
     verification failure. This scenario still does not have a safety
     impact.
   '''
}

// from gnatprove_optional.csv, row 2
Switch_Constraint SPARK_Switch_info {
   tool         = Tool.SPARK
   status       = Status.Allowed
   switches     = [
     Pattern.Prefix: "--info"
   ]
   rationale    = '''
     This switch can provide additional information but its presence
     or absence cannot lead to false negatives in verification
     results.
   '''
}

// from gnatprove_optional.csv, row 3
Switch_Constraint SPARK_Switch_j {
   tool         = Tool.SPARK
   status       = Status.Allowed
   switches     = [
     Pattern.Prefix: "-j"
   ]
   rationale    = '''
     This switch affects proof performance, but its presence or
     absence cannot lead to false negatives in verification results.
   '''
}

// from gnatprove_optional.csv, row 4
Switch_Constraint SPARK_Switch_level {
   tool         = Tool.SPARK
   status       = Status.Allowed
   switches     = [
     Pattern.Prefix: "--level"
   ]
   rationale    = '''
     This switch can control when GNATprove determines that it is
     unable to complete verification, but cannot lead to false
     negatives in verification results. This switch can control which
     provers are used, but cannot be used to select a
     non-safety-qualified prover. This switch can control whether
     counterexamples are produced, but see above for why that is not
     of concern.
   '''
}

// from gnatprove_optional.csv, row 5
Switch_Constraint SPARK_Switch_quiet {
   tool         = Tool.SPARK
   status       = Status.Allowed
   switches     = [
     Pattern.Prefix: "--quiet"
   ]
   rationale    = '''
     This switch hides some output but will not mask a verification
     failure.
   '''
}

// from gnatprove_optional.csv, row 6
Switch_Constraint SPARK_Switch_Group_6 {
   tool         = Tool.SPARK
   status       = Status.Allowed
   switches     = [
     Pattern.Prefix: "--memlimit",
     Pattern.Prefix: "--steps",
     Pattern.Prefix: "--timeout"
   ]
   rationale    = '''
     These switches can control when GNATprove determines that it is
     unable to complete verification, but these switches cannot lead
     to false negatives in verification results.
   '''
}

// from gnatprove_optional.csv, row 7
Switch_Constraint SPARK_Switch_mode {
   tool         = Tool.SPARK
   status       = Status.Allowed
   switches     = [
     Pattern.Prefix: "--mode=all"
   ]
   rationale    = '''
     This switch requests the default behavior of GNATprove, which is
     to do full checking for compliance with SPARK restrictions, full
     flow analysis, and full proof.
   '''
}

// from gnatprove_optional.csv, row 8
Switch_Constraint SPARK_Switch_output {
   tool         = Tool.SPARK
   status       = Status.Allowed
   switches     = [
     Pattern.Prefix: "--output"
   ]
   rationale    = '''
     This switch affects the format of the output but will not mask a
     verification failure.
   '''
}

// from gnatprove_optional.csv, row 9
Switch_Constraint SPARK_Switch_prover {
   tool         = Tool.SPARK
   status       = Status.Allowed
   switches     = [
     // (or any subset of these)
     Pattern.Prefix: "--prover=altergo,cvc5,z3"
   ]
   rationale    = '''
     GNATprove's use of the Alt-Ergo, CVC5, and Z3 provers is
     safety-qualified, and GNATprove does not use any other provers
     unless specifically directed to do so with the --prover=...
     switch.
   '''
}

// from gnatprove_optional.csv, row 10
Switch_Constraint SPARK_Switch_verbose {
   tool         = Tool.SPARK
   status       = Status.Allowed
   switches     = [
     Pattern.Prefix: "--verbose"
   ]
   rationale    = '''
     This switch reports some additional output but will not mask a
     verification failure.
   '''
}

// from gnatprove_required.csv, row 1
Switch_Constraint SPARK_Switch_checks_as_errors {
   tool         = Tool.SPARK
   status       = Status.Required
   switches     = [
     Pattern.Prefix: "--checks-as-errors=on"
   ]
   rationale    = '''
     In this process, GNATprove check messages are reviewed via
     diagnostic justifications, not via gnatprove output. This switch
     ensures that any check message will result in gnatprove not
     exiting without an error code.
   '''
}

// from gnatprove_required.csv, row 2
Switch_Constraint SPARK_Switch_warnings {
   tool         = Tool.SPARK
   status       = Status.Required
   switches     = [
     Pattern.Prefix: "--warnings=error"
   ]
   rationale    = '''
     Some GNATprove warnings are used to identify potential violations
     of GNATprove assumptions, each of which requires manual review to
     ensure the violations will not lead to GNATprove false negatives.
     This switch ensures that any such potential violation will result
     in gnatprove not exiting without an error code.
   '''
}

// from gnatprove_required.csv, row 3
Switch_Constraint SPARK_Switch_P {
   tool         = Tool.SPARK
   status       = Status.Required
   switches     = [
     // <project-file.gpr>
     Pattern.Prefix: "-P"
   ]
   rationale    = '''
     The use of -P is part of every documented method for specifying
     which compilation units to analyze.
   '''
}

// from gnatprove_required.csv, row 4
Switch_Constraint SPARK_Switch_Uppercase_U {
   tool         = Tool.SPARK
   status       = Status.Required
   switches     = [
     Pattern.Prefix: "-U"
   ]
   rationale    = '''
     Without -U, GNATprove will not necessarily analyze all the units
     that are part of the project. GNATprove specifically behaves as
     follows when invoked without -U: If specific source files are
     identified on the command line, then GNATprove will only analyze
     the units containing those source files, even if source files
     from other units are included in the project file. (GNATprove
     will additionally analyze their dependencies if also invoked with
     -u, but this still leaves open the possibility that some of the
     units will be missed). If specific source files are not
     identified on the command line, then GNATprove will only analyze
     main units and the units they depend on.
   '''
}
