/*
 * Copyright (C) 2024 - 2025 NVIDIA CORPORATION & AFFILIATES
 * Copyright (C) 2021 - 2024 AdaCore
 *
 * Permission is granted to copy, distribute and/or modify this document
 * under the terms of the GNU Free Documentation License, Version 1.3 or
 * any later version published by the Free Software Foundation; with the
 * Invariant Sections being "Attribution", with no Front-Cover
 * Texts, and no Back-Cover Texts.  A copy of the license is included in
 * the section entitled "GNU Free Documentation License".
 */

package Worksheet
import Checklist

section "Comprehensibility" {

  Item in_context_comprehensible {
    scope = Checklist.Scope.All
    text = '''
      Is all of the code in-context-comprehensible to the reviewer?
    '''
  }

  Item guidelines_compliant {
    scope = Checklist.Scope.All
    text = '''
      Does all the code fully observe the fragments of the Ada/SPARK
      Guidelines identified therein as manually enforced?
    '''
  }

  Item no_magic_numbers {
    scope = Checklist.Scope.All
    text = '''
      Does the code use symbolic names for constants where appropriate
      (instead of hard-coding constants in the code)?
    '''
  }

  Item comments_do_not_lie {
    scope = Checklist.Scope.All
    text = '''
      Are all the comments in the code consistent with the code
      itself?
    '''
  }

  Item sufficient_comments {
    scope = Checklist.Scope.All
    text = """
      In the reviewer's estimation, are there sufficient code comments
      to enable the review to efficiently comprehend the code?
    """
  }

  Item clean_code {
    scope = Checklist.Scope.All
    text = """
      Given the complexity of the unit's requirements, and in the
      reviewer's estimation, is the code not unreasonably difficult to
      verify against the requirements and design?
    """
  }

}

section "Correctness" {

  Item no_hidden_functionality  {
    scope = Checklist.Scope.Not_Platinum
    text = '''
      Does the code limit itself to the behavior and properties
      specified in the unit requirements and unit design?
    '''
  }

  Item only_allowed_dependencies  {
    scope = Checklist.Scope.Not_Platinum
    text = '''
      Does the code limit its use of ``with`` to package specifications
      that are within the scope of the unit (external packages of
      interface specifications provided/used by the software unit and
      internal packages of the unit itself)?

      (This question exists to catch Ada code in a software
      unit that erroneously uses an interface that the
      software unit is not permitted to use.)
    '''
  }

  Item requirements_met {
    scope = Checklist.Scope.Not_Platinum
    text = '''
      Does each subprogram in the code satisfy all the
      non-formally-verified unit requirements imposed on the
      subprogram, all the non-formally-verified unit design
      constraints imposed on the subprogram, and all the claims made
      in unit design documentation fragments concerning the
      subprogram?
    '''
  }

  Item guilty_until_proven_innocent  {
    scope = Checklist.Scope.Not_Platinum
    text = '''
      Has the reviewer approached the code from the
      perspective of assuming the code has bugs until the
      reviewer confirms otherwise?

      This question exists to remind engineers reviewing
      code that they are not to make any assumptions about
      the correctness of the code, e.g. based on the skill
      of the authors of the code. Regardless of where code
      comes from, code reviewers are to assume the code is
      incorrect until shown otherwise.
    '''
  }

  Item no_bugs_found {
    scope = Checklist.Scope.Not_Platinum
    text = '''
      Has the reviewer thoroughly studied all the software unit
      requirements and software unit files (especially ADS and ADB
      file) and been unable to find any bugs in the code?
    '''
  }

  Item assumptions_documented {
    scope = Checklist.Scope.Not_Platinum
    text = '''
      Are all assumptions made by the code captured as unit
      requirements or unit design fragments?
    '''
  }

}

section "Robustness" {

  Item input_validation {
    scope = Checklist.Scope.Not_Platinum
    text = '''
      Does each subprogram perform plausibility checks to ensure that
      input parameters comply with non-formal preconditions?
    '''
  }

  Item termination {
    scope = Checklist.Scope.Not_Platinum
    text = '''
      For each subprogram not marked ``Forward_Progress``,
      ``Always_Terminates``, or ``No_Return``, do all loops and
      recursions terminate?
    '''
  }

  Item exceptions {
    scope = Checklist.Scope.Ada
    text = '''
      For each call to a subprogram that can raise an exception, does
      the caller handle the possible exceptions?
    '''
  }

}
