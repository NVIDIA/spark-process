/*
 * Copyright (C) 2024 - 2025 NVIDIA CORPORATION & AFFILIATES
 * Copyright (C) 2021 - 2024 AdaCore
 *
 * Permission is granted to copy, distribute and/or modify this document
 * under the terms of the GNU Free Documentation License, Version 1.3 or
 * any later version published by the Free Software Foundation; with the
 * Invariant Sections being "Attribution", with no Front-Cover
 * Texts, and no Back-Cover Texts.  A copy of the license is included in
 * the section entitled "GNU Free Documentation License".
 */

package Checklist
import Steps

Item item_1_1_1 {
  automatable = true
  step        = Steps.ID.Identify_External_Packages
  scope       = Scope.All
  priority    = Priority.Medium
  ext_review  = false

  text = '''
    For each software interface provided or used by the Ada
    software unit (as determined by the software
    architectural design), does the software interface
    specification clearly indicate whether or not the
    software interface is expected to be specified per this
    process (in the form of ADS files)?

    **Rationale**: To start off, we need to identify which
    software interface specifications to verify with this process.
  '''
}

Item item_1_1_2 {
  automatable = true
  step        = Steps.ID.Identify_External_Packages
  step_to     = Steps.ID.Verify_Requirement_Necessity
  scope       = Scope.All
  priority    = Priority.Medium
  ext_review  = false

  text = '''
    For each software interface identified in
    checklist question 1 as being specified per this process
    (in the form of ADS files), did the developers complete
    an instance of the per-software-interface checklist in
    the next section, where that instance covers the
    software interface?

    Note: Multiple software interfaces can be covered by the
    same completed per-software-interface checklist.

    **Rationale**: The developers must complete the checklist for
    each software interface.
  '''
}
